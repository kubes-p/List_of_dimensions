(defun LM:StringSubst ( new old str / inc len )
    (setq len (strlen new)
          inc 0
    )
    (while (setq inc (vl-string-search old str inc))
        (setq str (vl-string-subst new old str inc)
              inc (+ inc len)
        )
    )
    str
)

(defun c:vykaz_vymer ( / file_ptr s entita typ_entity pre_precision vrcholy vrchol delka)
(vl-load-com)
	
	; --- upozornění kontroly polohy staničení a křivek
	
	(alert "Nutná kontrola polohy staničení a křivek kubatur: NEJNIŽŠÍ BOD KŘIVKY MUSÍ LEŽET POD STANIČENÍM ŘEZU, VE KTERÉM SE KŘIVKA NACHÁZÍ.\nPokud jsi tuto podmínku nezkontroloval, ukonči příkaz a proveď jej po kontrole.\nPokud je vše v pořádku, vyber najednou všechna staničení i křivky pro výpočet kubatur.")

	; --- nová verze lispu 2.0 (Excel 2.1)
	
	(alert "Verze 2.0\nNení nutné Mtexty staničení rozbíjet na text.\nOd verze 2.0 je možné konkrétním obsahem názvu hladin kubatur předem připravit jednotky výstupu. Není to podmínkou, pokud některé (nebo všechny) hladiny koncovky +m2+/+m+ nemají, u neoznačených hladin bude výstup stejný jako dříve plocha i objem (viz manuál). ")
	
	; --- vytvoření souboru txt
	
	(setq file_ptr (open (strcat (getvar 'dwgprefix) "Vykaz_vymer_pricne_rezy.txt") "w"))
	
	; --- práce s výběrem, zápis do souboru
	
	(setq pre_precision (getvar "luprec"))
	(setvar "luprec" 6)
	(princ "Vyber všechna staničení a všechny křivky pro výpočet kubatur.")
	    (if (setq s (ssget '((0 . "Text,Mtext,Lwpolyline,Line")) ))
		(progn
		    (setq i 0
			  n (sslength s)
		    )
		    (while (< i n)
			(setq entita (ssname s i)
			      typ_entity (cdr (assoc 0 (entget entita)))
			      i (+ 1 i)
			)
			;(print typ_entity)
			(if (or (= typ_entity "TEXT") (= typ_entity "MTEXT"))
			    (progn
				;(print "staničení")
				(setq	x (cdr (assoc 0 (entget entita)))				; --- typ entity
					x (strcat x ";" (rtos (caddr (assoc 10 (entget entita))) 2) )	; --- y textu
					x (strcat x ";" (cdr (assoc 8 (entget entita))))		; --- hlad stan
					;x (strcat x ";" (cdr (assoc 1 (entget entita))))		; --- hodn stan
					x (strcat x ";" (LM:StringSubst "." "," (cdr (assoc 1 (entget entita)))   )   )		; --- hodn stan
				)
				(print x)
				(write-line x file_ptr)
			    )
			    (progn
				(if (= typ_entity "LINE")
				(progn
				    ;(print "úsečka")
				    (setq y (rtos (distance (cdr (assoc 10 (entget entita))) (cdr (assoc 11 (entget entita))) ) 2))
				    ;(print y)								; --- délka úsečky
				    (setq x (cdr (assoc 0 (entget entita)))				; --- typ entity
					  w (cdr (assoc 8 (entget entita)))				; --- hl kubatury
					  vrchol (car (cddr (assoc 10 (entget entita))))
					  vrcholk (car (cddr (assoc 11 (entget entita))))
				    )
				    (if (< vrcholk vrchol)
					(setq vrchol vrcholk)
				    )
				    (setq x (strcat x ";" (rtos vrchol) )
					  x (strcat x ";" w)
					  x (strcat x ";" y)
					  x (strcat x ";0.0")
				    )
				    (print x)
				    (write-line x file_ptr)
				)
				(progn
				;(print "křivka kubatury")
				(setq	x (cdr (assoc 0 (entget entita)))				; --- typ entity
					w (cdr (assoc 8 (entget entita)))				; --- hl kubatury
				)
				
				(command "_.area" "_o" entita)
				(setq	y (rtos (getvar "perimeter") 2)					; --- obvod křivky
					z (rtos (getvar "area") 2)					; --- obsah křivky
				)
				
				(setq	vrcholy(list)
					enlist (entget entita)
					j 0
				)
				(foreach a enlist
				    (if (= 10 (car a))
					(progn
					    (setq   vrcholy (append vrcholy (list (cdr a)))
						    j (+ 1 j)
					    )
					)
				    )
				)
				;(print j)
				;(print vrcholy)
				;(print (car (cdr (nth 0 vrcholy))))
				;(print (car (cdr (nth (- j 1) vrcholy))))
				(setq   k 0					; --- y souřadnice "nejnižšího" vrcholu
					vrchol (car (cdr (nth k vrcholy)))
				)
				;(print vrchol)
				(while (< k j)
				    (setq vrcholk (car (cdr (nth k vrcholy)))
				    )
				    ;(print vrcholk)
				    (if (< vrcholk vrchol)
					(progn
					    (setq vrchol vrcholk
					    )
					)
				    )
				    (setq k (+ 1 k)
				    )
				    ;(print vrchol)
				)
				(print (rtos vrchol))
				(print w)
				(print y)
				(print z)
				(setq	x (strcat x ";" (rtos vrchol) )
					x (strcat x ";" w)
					x (strcat x ";" y)
					x (strcat x ";" z)
				)
				(print x)
				(write-line x file_ptr)
				)
				)
			    )
			)
		    )
		)
	    )
	(close file_ptr)
	(setvar "luprec" pre_precision)
	
	; --- zpráva o ukončení

	(alert "Data byla exportována. Vytvořen soubor Vykaz_vymer_pricne_rezy.txt.\nNyní ve složce výkresu otevři sešit Vykaz_vymer_vychozi.xlsm")
	(princ)
)
